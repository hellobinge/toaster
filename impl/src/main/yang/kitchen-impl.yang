module kitchen-impl {
    yang-version 1;
    namespace "urn:opendaylight:params:xml:ns:yang:kitchen:impl";
    prefix "kitchen-impl";

    import config { prefix config; revision-date 2013-04-05; }
    import opendaylight-md-sal-binding { prefix md-sal-binding; revision-date 2013-10-28; }
    import rpc-context { prefix rpcx; revision-date 2013-06-17; }

    description
        "Service definition for kitchen project";

    revision "2014-12-10" {
        description
            "Initial revision";
    }

    identity kitchen {
        base config:module-type;
        config:java-name-prefix Kitchen;
    }

    augment "/config:modules/config:module/config:configuration" {
        case kitchen {
            when "/config:modules/config:module/config:type = 'kitchen'";
            container broker {
                uses config:service-ref {
                    refine type {
                        mandatory true;
                        config:required-identity md-sal-binding:binding-broker-osgi-registry;
                    }
                }
            }
        }
    }

}
