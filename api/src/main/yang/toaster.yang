module toaster {
    yang-version 1;
    namespace "urn:opendaylight:params:xml:ns:yang:toaster";
    prefix "toaster";

    revision "2015-01-05" {
        description "Initial revision of toaster model";
    }

    identity toast-type {}

    identity white-bread {
        base toast-type;
    }

    identity wheat-bread {
        base toast-type;
    }

    identity wonder-bread {
        base toast-type;
    }

    typedef DisplayString {
        type string {
            length "0 .. 255";
        }
    }

    container toaster {
        leaf toasterManufacturer {
            type DisplayString;
            config false;
            mandatory true;
        }
        leaf toasterModelNumber {
            type DisplayString;
            config false;
            mandatory true;
        }
        leaf toasterStatus {
            type enumeration {
                enum "up" {
                    value 1;
                }
                enum "down" {
                    value 2;
                }
            }
            config false;
            mandatory true;
        }
        leaf darknessFactor {
            type uint32;
            config true;
            default 1000;
        }
    }

    rpc make-toast {
        input {
            leaf toasterDoneness {
                type uint32 {
                    range "1 .. 10";
                }
                default 5;
            }
            leaf toasterToastType {
                type identityref {
                    base toast-type;
                }
                default "wheat-bread";
            }
        }
    }

    rpc cancel-toast {
    }

    rpc restock-toaster {
        input {
            leaf amountOfBreadToStock {
                type uint32;
            }
        }
    }

    notification toasterOutofBread {
    }

    notification toasterRestocked {
        leaf amountOfBread {
            type uint32;
        }
    }

}
